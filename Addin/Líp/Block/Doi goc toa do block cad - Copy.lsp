;;; BM_BasePoint.lsp
;;; Chức năng: Đổi gốc tọa độ (base point) của block
;;; Cách dùng: APPLOAD, gõ BMBASEPOINT
;;; Sửa lỗi: Chỉ chọn 1 lần block để lấy tên và UCS tham chiếu, giảm bớt prompt chọn.
;;; Cập nhật: Thêm xử lý scale sau khi đổi base point (giữ nguyên/nhập mới/unit factor 25.4 inch→mm),
;;;           đặt trong bm-change-basepoint để scope biến đúng; dùng getkword; fix extra paren.

(vl-load-com)

(defun bm-print (s) (princ (strcat "\n" s)))

(defun bm-get-block-name-and-ref (/ ent ename edata blkname)
  (setq ent (entsel "\nChọn một block (INSERT) để thay đổi base point: "))
  (if (not ent)
    (progn (bm-print "❌ Bạn chưa chọn block. Thoát.") (exit))
  )
  (setq ename (car ent))
  (setq edata (entget ename))
  (setq blkname (cdr (assoc 2 edata)))
  (if (not blkname)
    (progn (bm-print "❌ Không xác định được tên block.") (exit))
  )
  (list blkname ename) ; Trả về tên và entity ref
)

(defun bm-get-all-inserts-by-name (name / ss)
  (ssget "X" (list (cons 0 "INSERT") (cons 2 name)))
)

(defun bm-change-basepoint (blkname ref-ent / DIEMCHENMOI luubatdiem doituong TENKHOI TENKHOIMOI TYLEX TYLEY DIEMTINH XDIEMTINH YDIEMTINH DAICHUAS GOCCHUAS DIEMCHENTUONGDOI XX L M DTs DTMs TYLEX1 TYLEY1 DIEMDOI scaleChoice newScale newScaleFactor scaleX scaleY DTMs)
  (command "undo" "be")
  (setq doituong1 (list ref-ent))
  (command "ucs" "ob" ref-ent)
  (setq DIEMCHENMOI (getpoint "\nChọn điểm gốc mới (local UCS của instance): "))
  (if (not DIEMCHENMOI)
    (progn (bm-print "❌ Không chọn điểm gốc mới.") (exit))
  )
  (setq luubatdiem (getvar "osmode"))
  (setvar "osmode" 0)
  (command "layer" "s" 0 "")
  (setq doituong (entget ref-ent))
  (setq TENKHOI blkname)
  (setq TENKHOIMOI (strcat TENKHOI "TAOTHEM"))
  (setq TYLEX (cdr (assoc 41 doituong)))
  (setq TYLEY (cdr (assoc 42 doituong)))
  (setq DIEMTINH (list (/ (car DIEMCHENMOI) TYLEX) (/ (cadr DIEMCHENMOI) TYLEY)))
  (setq XDIEMTINH (car DIEMTINH))
  (setq YDIEMTINH (cadr DIEMTINH))
  (setq DAICHUAS (distance (list 0 0) DIEMTINH))
  (setq GOCCHUAS (angle (list 0 0) DIEMTINH))
  (setq DIEMCHENTUONGDOI (polar (list 0 0) GOCCHUAS DAICHUAS))
  (command ".INSERT" TENKHOI (list 0 0) 1 1 0)
  (command "EXPLODE" "last" "")
  (command "Block" TENKHOIMOI DIEMCHENTUONGDOI "Previous" "")
  (command "ucs" "p")
  (setq XX (bm-get-all-inserts-by-name TENKHOI))
  (setq L 0)
  (setq M (if XX (sslength XX) 0))
  (while (< L M)
    (setq DTs (ssname XX L))
    (setq DTMs (entget DTs))
    (command "ucs" "ob" DTs)
    (setq TYLEX1 (cdr (assoc 41 DTMs)))
    (setq TYLEY1 (cdr (assoc 42 DTMs)))
    (setq DIEMDOI (list (* XDIEMTINH TYLEX1) (* YDIEMTINH TYLEY1)))
    (setq DTMs (subst (cons 2 TENKHOIMOI) (assoc 2 DTMs) DTMs))
    (entmod DTMs)
    (setq DIEMDOI (trans DIEMDOI 1 0))
    (setq DTMs (subst (cons 10 DIEMDOI) (assoc 10 DTMs) DTMs))
    (entmod DTMs)
    (command "ucs" "p")
    (setq L (1+ L))
  )
  (setvar "osmode" luubatdiem)
  (command "Purge" "B" TENKHOI "Y" "Y")
  (command "rename" "b" TENKHOIMOI TENKHOI)
  (command "undo" "end")
  (bm-print (strcat "✅ Vừa chỉnh base point của block <" TENKHOI "> : " (itoa L) " đối tượng"))

  ;; === Scale xử lý sau khi đổi base point ===
  (bm-print "\nChọn cách xử lý scale:")
  (bm-print "1. Giữ nguyên scale hiện tại")
  (bm-print "2. Nhập scale mới")
  (bm-print "3. Scale theo unit factor 25.4 (inch → mm)")
  (initget "1 2 3")
  (setq scaleChoice (getkword "\nNhập lựa chọn [1/2/3] <1>: "))
  (if (null scaleChoice) (setq scaleChoice "1"))

  (if (not (member scaleChoice '("1" "2" "3")))
    (progn (bm-print "❌ Lựa chọn không hợp lệ. Giữ nguyên scale.") (setq scaleChoice "1")))

  (if (= scaleChoice "1")
    (bm-print "✅ Giữ nguyên scale hiện tại.")
    (progn
      (cond
        ((= scaleChoice "2")
          (setq newScale (getreal "\nNhập giá trị scale mới: "))
          (if (not (and (numberp newScale) (> newScale 0)))
            (progn (bm-print "❌ Scale không hợp lệ. Bỏ qua.") (exit))))
        ((= scaleChoice "3")
          (setq newScaleFactor 0.254)))
      
      (setq L 0)  ; Reset L cho loop scale
      (while (< L M)
        (setq DTs (ssname XX L))
        (if DTs
          (progn
            (setq DTMs (entget DTs))
            (setq scaleX (cdr (assoc 41 DTMs)))
            (setq scaleY (cdr (assoc 42 DTMs)))
            (if (null scaleX) (setq scaleX 1.0))
            (if (null scaleY) (setq scaleY 1.0))
            (cond
              ((= scaleChoice "2")
                (setq scaleX newScale)
                (setq scaleY newScale))
              ((= scaleChoice "3")
                (setq scaleX (* scaleX newScaleFactor))
                (setq scaleY (* scaleY newScaleFactor)))
            )
            (setq DTMs (subst (cons 41 scaleX) (assoc 41 DTMs) DTMs))
            (setq DTMs (subst (cons 42 scaleY) (assoc 42 DTMs) DTMs))
            (entmod DTMs)))
        (setq L (1+ L)))
      (bm-print (strcat "✅ Đã cập nhật scale cho " (itoa M) " instance."))))
  (princ)
)

(defun c:BMBASEPOINT (/ blkname-ref)
  (princ "\n=== BM_BasePoint: Đổi gốc tọa độ block ===")
  (setq blkname-ref (bm-get-block-name-and-ref))
  (setq blkname (car blkname-ref))
  (setq ref-ent (cadr blkname-ref))
  (bm-print (strcat "🔹 Block được chọn: " blkname))
  (bm-change-basepoint blkname ref-ent)
  (princ)
)

(princ "\nGõ BMBASEPOINT để chạy lệnh.")
(princ)
