; AutoLISP code for AutoCAD to delete Dimensions
; Updated: Load DCL from same folder instead of TEMP
; Reordered: 1=old4 (selected), 2=old2 (by layer), 3=old3 (MLEADER), 4=new (by layer+select), 5=old1 (all)
; Load this LISP with (load "dimdelete.lsp") or APPLOAD

; Main function
(defun c:dimdelete (/ dcl_id dcl-path layerlist layer lay ss i ent layname choice result layindex)
  (setq choice nil layindex nil)  ; Initialize globals
  (setq dcl-path "dimdelete.dcl")
  (if (or (not (findfile dcl-path)))
    (progn
      (alert "Không thể tìm thấy file DCL 'dimdelete.dcl' trong thư mục hiện tại. Đặt file cùng folder với LISP.")
      (exit)
    )
  )
  (setq dcl_id (load_dialog dcl-path))
  (if (not (new_dialog "dimdel" dcl_id))
    (progn
      (alert "Không load được hộp thoại.")
      (exit)
    )
  )

  ; Populate layer dropdown correctly
  (setq layerlist '())
  (if (setq layer (tblnext "LAYER" T))
    (progn
      (while layer
        (setq layerlist (cons (cdr (assoc 2 layer)) layerlist))
        (setq layer (tblnext "LAYER"))
      )
      (setq layerlist (reverse layerlist))
    )
  )
  (if layerlist
    (progn
      (start_list "layerlist" 3)  ; 3 = no multiple select
      (foreach lay layerlist
        (add_list lay)
      )
      (end_list)
      (set_tile "layerlist" "0")
    )
    (progn
      (start_list "layerlist" 3)
      (add_list "Không có layer")
      (end_list)
      (set_tile "layerlist" "0")
    )
  )

  ; Select default radio button to new #1
  (set_tile "selected_dim" "1")

  ; Action for OK: Set choice and layindex before closing
  (action_tile "accept"
    "(progn
       (setq choice (get_tile \"options\"))
       (setq layindex (get_tile \"layerlist\"))
       (done_dialog 1)
     )"
  )
  (action_tile "cancel" "(done_dialog 0)")

  (setq result (start_dialog))
  (unload_dialog dcl_id)

  ; Only execute if OK was pressed (result = 1)
  (if (= result 1)
    (progn
      ; Execute based on choice
      (cond
        ((= choice "selected_dim")
         (delete-selected-dim)
        )
        ((= choice "dim_by_layer")
         (if (and layindex layerlist (> (length layerlist) 0) (/= layindex ""))
           (progn
             (setq layname (nth (atoi layindex) layerlist))
             (if (and layname (/= layname "Không có layer"))
               (delete-dim-by-layer layname)
               (alert "Layer không hợp lệ.")
             )
           )
           (alert "Không có layer nào được chọn hoặc không có layer. Chọn chức năng khác.")
         )
        )
        ((= choice "dim_mleader")
         (delete-mleader)
        )
        ((= choice "dim_by_layer_select")
         (if (and layindex layerlist (> (length layerlist) 0) (/= layindex ""))
           (progn
             (setq layname (nth (atoi layindex) layerlist))
             (if (and layname (/= layname "Không có layer"))
               (delete-dim-by-layer-select layname)
               (alert "Layer không hợp lệ.")
             )
           )
           (alert "Không có layer nào được chọn hoặc không có layer. Chọn chức năng khác.")
         )
        )
        ((= choice "all_dim")
         (delete-all-dim)
        )
        (T
         (alert "Lựa chọn không hợp lệ. Mặc định xóa DIMENSION được chọn.")
         (delete-selected-dim)
        )
      )
    )
    (princ "\nĐã hủy lệnh.")
  )
  (princ)
)

; Function 1: Delete selected DIMENSION (old 4, now 1)
(defun delete-selected-dim (/ ss cnt)
  (princ "\nChọn các DIMENSION cần xóa (có thể quét chọn bằng window/crossing hoặc pick từng cái, Enter để kết thúc): ")
  (if (setq ss (ssget '((0 . "DIMENSION"))))
    (progn
      (setq cnt (sslength ss))
      (command "_.ERASE" ss "")
      (alert (strcat "Đã xóa " (itoa cnt) " DIMENSION được chọn."))
    )
    (alert "Không có DIMENSION nào được chọn.")
  )
  (princ)
)

; Function 2: Delete DIMENSION by layer (old 2, now 2)
(defun delete-dim-by-layer (layname / ss filter cnt)
  (setq filter (list '(0 . "DIMENSION") (cons 8 layname)))
  (if (setq ss (ssget "X" filter))
    (progn
      (setq cnt (sslength ss))
      (command "_.ERASE" ss "")
      (alert (strcat "Đã xóa " (itoa cnt) " DIMENSION trên layer " layname "."))
    )
    (alert (strcat "Không có DIMENSION nào trên layer " layname "."))
  )
)

; Function 3: Delete LEADER NOTE (MLEADER) (old 3, now 3)
(defun delete-mleader (/ ss cnt)
  (if (setq ss (ssget "X" '((0 . "MLEADER"))))
    (progn
      (setq cnt (sslength ss))
      (command "_.ERASE" ss "")
      (alert (strcat "Đã xóa " (itoa cnt) " LEADER NOTE (MLEADER)."))
    )
    (alert "Không có LEADER NOTE (MLEADER) nào trong bản vẽ.")
  )
)

; New Function 4: Delete DIMENSION by layer and selected area (based on 2 + selection like 1)
(defun delete-dim-by-layer-select (layname / filter ss cnt)
  (setq filter (list '(0 . "DIMENSION") (cons 8 layname)))
  (princ (strcat "\nChọn vùng DIMENSION trên layer " layname " (có thể quét chọn bằng window/crossing hoặc pick, Enter để kết thúc): "))
  (if (setq ss (ssget filter))
    (progn
      (setq cnt (sslength ss))
      (command "_.ERASE" ss "")
      (alert (strcat "Đã xóa " (itoa cnt) " DIMENSION trên layer " layname " trong vùng chọn."))
    )
    (alert (strcat "Không có DIMENSION nào được chọn trên layer " layname "."))
  )
  (princ)
)

; Function 5: Delete all DIMENSION (old 1, now 5)
(defun delete-all-dim (/ ss cnt)
  (if (setq ss (ssget "X" '((0 . "DIMENSION"))))
    (progn
      (setq cnt (sslength ss))
      (command "_.ERASE" ss "")
      (alert (strcat "Đã xóa " (itoa cnt) " DIMENSION."))
    )
    (alert "Không có DIMENSION nào trong bản vẽ.")
  )
)

(princ "\nGõ DIMDELETE để chạy lệnh. (Cập nhật: Tách DCL riêng; Thêm chức năng 4 - Xóa theo layer + vùng; Đổi thứ tự 1/4/5)")
(princ)
